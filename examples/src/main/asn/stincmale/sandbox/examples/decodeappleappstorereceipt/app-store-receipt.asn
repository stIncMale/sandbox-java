ReceiptModule DEFINITIONS ::=
BEGIN

ReceiptAttribute ::= SEQUENCE {
  type    INTEGER,
  version INTEGER,
  value   OCTET STRING
}

Payload ::= SET OF ReceiptAttribute

InAppAttribute ::= SEQUENCE {
  type                   INTEGER,
  version                INTEGER,
  value                  OCTET STRING
}

InAppReceipt ::= SET OF InAppAttribute

END
